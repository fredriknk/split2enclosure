"""Launch the Split2Enclosure dialog from an installed add-on folder."""

try:
    from freecad.Split2Enclosure.command import run
except ImportError as exc:
    raise RuntimeError(
        "Install the complete Split2Enclosure add-on in FreeCAD's Mod directory; "
        "the macro launcher cannot run without its Python package."
    ) from exc

run()
